FME workspace DevOpsDemo.fmw

Creator
    GEOMTYPE = Geometry Object
    NUM = 1
    CREATED -> FeatureReader [INITIATOR]
FeatureReader
    ATTRIBUTES = public.AddressPoints,"AddressId,CivicNo,StreetName,TaxCoord,SiteId"
    ATTR_ACCUM_MODE = Only Use Result
    CLIP_TO_ENVELOPE = NO
    COMBINE_GEOM = Use Result
    DATASET = $(fmedataDP)
    FEATURETYPES = public.AddressPoints
    FORMAT = POSTGIS
    GEOMETRY_TYPES = public.AddressPoints,"""geom,fme_area,fme_collection,fme_line,fme_point,fme_surface"""
    INITIATOR_FIRST_OUTPUT = default
    INPUT_PORT_INITIATOR_CONNECTED = CONNECTED
    INTERACT = NONE
    MAX_FEATURES = 112
    ORDER_RESULTS = No
    OUTPUT_ADD_SCHEMA_ATTRIBUTES = NO
    OUTPUT_FEATURES_DISPLAY = Schema and Data Features
    OUTPUT_USE_SCHEMA_CACHE = YES
    POSTGIS_CREATE_FEATURE_TABLES_FROM_DATA = Yes
    POSTGIS_DISABLE_COLLECTION_SPLITTING = yes
    POSTGIS_FEATURES_PER_FETCH = 10000
    POSTGIS_NAMED_CONNECTION = $(fmedataDP)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    READER_BEHAVIOR = SELECTFEATTYPES
    public.AddressPoints -> Tester
Tester
    BOOL_OP = OR
    TEST_CLAUSE = CASE_INSENSITIVE_TEST @Value(StreetName) BEGINS_WITH B
    TEST_MODE = CASE_INSENSITIVE_TEST
    PASSED -> AttributeCreator
AttributeCreator
    ATTR_TABLE = SET_TO PATHexcel (varchar(200)) = $(FME_SHAREDRESOURCE_DATA)/test/Output/$(ENV)
    INPUT_PORT_CONNECTED = CONNECTED
    -> FeatureWriter [Output]
FeatureWriter
    CONFIG_PARAMETERS = ESCAPE_COMMAS_IN_FTP_FORMAT_PARAMETERS,no
    DATASET = @Value(PATHexcel)/AddressPoints.xlsx
    DATASET_ATTR = _dataset
    FEATURE_TYPE_LIST_ATTR = _feature_types
    FORMAT = XLSXW
    TOTAL_FEATURES_WRITTEN_ATTR = _total_features_written
    XLSXW_ALWAYS_CREATE_FEATURE_TYPES = NO
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert
